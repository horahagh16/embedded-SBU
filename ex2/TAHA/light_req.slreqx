# light_req

## car's green: count gratter or equal 60 green light is on (Functional)

## pending state: pedestran is comeing and count lower than 60 , pending state is on (Functional)

## yellow: when the satate is pending count gratter or equal 60 , signal yellow is on (Functional)

## red's car: when in yellow state and count gratter or equal 5 sigR is on (Functional)

## yellow's car: when in green state and have pedestrian and count gratter or equal 60 , sigY is on (Functional)

## pedestrian's light: when in pedestrian's green and count gratter or equal 55 , pedR is on (Functional)

## pedestrian's red light: when in pedestrian's red and sigR is one, pedG is on (Functional)
