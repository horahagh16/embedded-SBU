# requirement

## Red to Green: cars light -> green (Functional)
در حالت Red اگر count بزرگتر مساوی 60 شود ، چراغ سبز روشن میشود و SigG فعال میشود

## Pending to Yellow: cars light -> Yellow (Functional)
زمانی که در حالت pending باشیم و count بزرگتر مساوی 60 شود ، چراغ زرد روشن میشود وSigY فعال میشود

## Green to Pending: go to pending (Functional)
در حالت Green اگر عابرپیاده بیاید و count کوچکتر از 60 باشد ، به pending میرویم

## Yellow to Red: cars light -> Red (Functional)
در حالت Yellow اگر count بزرگتر مسساوی 5 شود ، چراغ قرمز میشود و SigR فعال میشود

## Green to Yellow: cars light -> Yellow (Functional)
در حالت Green اگر عابرپیاده بیاید و countبزرگتر مساوی 60 باشد ، چراغ زرد میشود و SigY فعال میشود

## Green to Red for Pedestrian: Pedestrian light -> Red (Functional)
اگر چراغ عابرپیاده سبز باشد و pcount بزرگتر مساوی 55 شود ، چراغ قرمز میشود و PedR فعال میشود

## Red to Green for Pedestrian: Pedestrian light -> Green (Functional)
اگر چراغ عابرپیاده قرمز باشد و SigR فعال شود ، چراغ سبز میشود
